(defun _Val (e / s) 
  (if (setq s (cdr (assoc 1 (entget e)))) 
    (list (vlax-ename->vla-object e) s (Cdr (assoc 8 (entget e))))
  )
)

(Defun _execution (a b) 
  (mapcar 
    '(lambda (p v) 
       (vlax-put (car a) p v)
     )
    '("TextString" "Layer")
    (cdr b)
  )
)
(Defun _Operation (m / source SourceData target targetData) 
  (while 
    (and 
      (setq source (car (nentsel "\nSelect text source")))
      (setq SourceData (_val source))
      (setq target (car (nentsel "\nSelect text target")))
      (setq targetData (_val target))
    )
    (_execution targetData SourceData)
    (if m (_execution SourceData targetData))
  )
  (princ)
)
(Defun c:CopyTextTo nil (_Operation nil))
(Defun c:SwapTextTo nil (_Operation t))
