;Este Lisp ha sido desarrollado para ayudar en la obtencion de dimensiones de lines y polilineas
;encuentra mas en mi blog: 

;################################################################
         ; INSTITUTO POLITECNICO NACIONAL
         ; canal youtube "TEXCAL GUERRERO"
         ; SABADO 23 MAYO 2015
         ; LLAMAR A LA FUNCION CON EL COMANDO ''MLIN''
;################################################################


(vl-load-com)

(defun c:MLin()
        (alert "############## \INSTITU POLITECNICO NACIONAL MEXICO
         \n LA TECNICA AL SERVICIO DE LA PATRIA \n SABADO 23 MAYO 2015 \n ############## ")
	(setvar "luprec" 2)
	(Cre_Lay "dist" 6)
	(setq disttot 0)
	(setq lines(ssget (list (cons 0 "line,pline,lwpolyline"))))
	(setq ctr 0)
	(if (/= lines nil)
		(progn
			(setq len(sslength lines))
			(repeat len
				(setq ent(ssname lines ctr))
				(setq pntList(ReadPline ent))
				(setq ptCntr 0)
				(repeat (1- (length pntList))
					(setq fpoint(nth ptCntr pntList))
					(setq epoint(nth (1+ ptCntr) pntList))
					(setq thr(distance fpoint epoint))
					(setq fou(angle fpoint epoint))
					(setq ang(* (/ fou pi) 180))
					(if (and (>= ang 90) (<= ang 270)) (setq ang(rtos (+ ang 180))) (setq ang(rtos ang)))
					(setq txt_ins(MidP fpoint epoint))
					(command "._Text" "j" "bc" txt_ins "1.75" ang (rtos thr))
					(command "._Change" (entlast) "" "p" "la" "dist" "")		
					(setq disttot(+ disttot (distance fpoint epoint)))
					(setq ptCntr(1+ ptCntr))
				)
				(setq ctr(1+ ctr))
			)
			(princ (strcat "\nTotal distance :"  (rtos disttot 2 4)))
		)
	)
	(princ)
)
(princ "\nType \"MLin\" to Measure each Segment of the Polyline.")  (princ)

; Function to find the mid point of two points.
(defun MidP(midp_fpo midp_spo)
	(setq midp_mpo(list (/ (+ (car midp_fpo) (car midp_spo)) 2) (/ (+ (cadr midp_fpo) (cadr midp_spo)) 2)))
)

;Function to Create a Layer with given color.
(defun Cre_Lay(lay_layn lay_laycol)
	(if (= (tblsearch "Layer" lay_layn) nil)
		(command "._Layer" "n" lay_layn "c" lay_laycol lay_layn "")
		(command "._Layer" "t" lay_layn "on" lay_layn "c" lay_laycol lay_layn "")
	)
	(princ)
)

;Function to Read Vertices of Selected Lines.
(defun ReadPline(imp_Ent)
	(setq glb_obj(vlax-ename->vla-object imp_Ent))
	(setq glb_PntCnt(vlax-curve-getEndParam glb_obj))
	(setq returnPTList '())
	(setq ptCntr 1)
	(setq glb_oName(vlax-get-property glb_obj 'ObjectName))
	(setq glb_OClosed nil)
	(if (= glb_oName "AcDbLine")
		(progn
			(setq glb_EnDetails(entget imp_Ent))
			(setq big_Point3d(cdr (assoc 10 glb_EnDetails)))
			(setq end_Point3d(cdr (assoc 11 glb_EnDetails)))
			(setq returnPTList(append returnPTList (list big_Point3d)))
			(setq returnPTList(append returnPTList (list end_point3d)))
		)
		(progn
			(setq glb_OClosed(vlax-curve-isClosed glb_obj))
			(setq glb_2dDist 0)
			(setq old_Point nil)
			(repeat (1+ (fix glb_PntCnt))
				(setq cur_Point3d(vlax-curve-getPointAtParam glb_obj (1- ptCntr)))
				(setq returnPTList(append returnPTList (list cur_Point3d)))
				(setq ptCntr(1+ ptCntr))
			)
		)
	)
	(setq return returnPTList)
)
