(defun C:CCAPAS ();V1.0 
   (command "_Layer" "_m" "CAT_TAPS" "_c" "BLANCO" "CAT_TAPS" "T" "CONTINUOUS" "CAT_TAPS" "g" "0.09" "CAT_TAPS" "")
   (command "_Layer" "_m" "CAT_DIVISORES" "_c" "BLANCO" "CAT_DIVISORES" "T" "CONTINUOUS" "CAT_DIVISORES" "g" "0.09" "CAT_DIVISORES" "")
   (command "_Layer" "_m" "CAT_AMPLIFICADORES" "_c" "BLANCO" "CAT_AMPLIFICADORES" "T" "CONTINUOUS" "CAT_AMPLIFICADORES" "g" "0.09" "CAT_AMPLIFICADORES" "")
   (command "_Layer" "_m" "CAT_CALLES" "_c" "AZUL" "CAT_CALLES" "T" "CONTINUOUS" "CAT_CALLES" "g" "0.09" "CAT_CALLES" "")
   (command "_Layer" "_m" "CAT_LIMITE NODO" "_c" "AZUL" "CAT_LIMITE NODO" "T" "CONTINUOUS" "CAT_LIMITE NODO" "g" "1.00" "CAT_LIMITE NODO" "")
   (command "_Layer" "_m" "CAT_TIERRAS" "_c" "AZUL" "CAT_TIERRAS" "T" "CONTINUOUS" "CAT_TIERRAS" "g" "0.09" "CAT_TIERRAS" "")
   (command "_Layer" "_m" "CAT_POSTES" "_c" "96" "CAT_POSTES" "T" "CONTINUOUS" "CAT_POSTES" "g" "0.09" "CAT_POSTES" "")
   (command "_Layer" "_m" "CAT_POSTES PROYECTADOS" "_c" "96" "CAT_POSTES PROYECTADOS" "T" "CONTINUOUS" "CAT_POSTES PROYECTADOS" "g" "0.09" "CAT_POSTES PROYECTADOS" "")
   (command "_Layer" "_m" "CAT_ANCLAS EXISTENTES" "_c" "AZUL" "CAT_ANCLAS EXISTENTES" "T" "CONTINUOUS" "CAT_ANCLAS EXISTENTES" "g" "0.09" "CAT_ANCLAS EXISTENTES" "")
   (command "_Layer" "_m" "CAT_ANCLAS PROYECTADAS" "_c" "AZUL" "CAT_ANCLAS PROYECTADAS" "T" "CONTINUOUS" "CAT_ANCLAS PROYECTADAS" "g" "0.09" "CAT_ANCLAS PROYECTADAS" "")
   (command "_Layer" "_m" "CAT_REFERENCIAS" "_c" "BLANCO" "CAT_REFERENCIAS" "T" "CONTINUOUS" "CAT_REFERENCIAS" "g" "0.09" "CAT_REFERENCIAS" "")
   (command "_Layer" "_m" "CAT_ALIMENTA" "_c" "30" "CAT_ALIMENTA" "T" "CONTINUOUS" "CAT_ALIMENTA" "g" "0.09" "CAT_ALIMENTA" "")
   (command "_Layer" "_m" "CAT_LINEA RED EXISTENTE" "_c" "VERDE" "CAT_LINEA RED EXISTENTE" "T" "CONTINUOUS" "CAT_LINEA RED EXISTENTE" "g" "0.09" "CAT_LINEA RED EXISTENTE" "")
   (command "_Layer" "_m" "CAT_DISTANCIA POSTES" "_c" "VERDE" "CAT_DISTANCIA POSTES" "T" "CONTINUOUS" "CAT_DISTANCIA POSTES" "g" "0.09" "CAT_DISTANCIA POSTES" "")
   (command "_Layer" "_m" "CAT_OBSERVACION POSTES" "_c" "BLANCO" "CAT_OBSERVACION POSTES" "T" "CONTINUOUS" "CAT_OBSERVACION POSTES" "g" "0.09" "CAT_OBSERVACION POSTES" "")
   (command "_Layer" "_m" "CAT_TERMINALES" "_c" "BLANCO" "CAT_TERMINALES" "T" "CONTINUOUS" "CAT_TERMINALES" "g" "0.09" "CAT_TERMINALES" "")
   (command "_Layer" "_m" "CAT_CASAS ALIMENTADAS" "_c" "VERDE" "CAT_CASAS ALIMENTADAS" "T" "CONTINUOUS" "CAT_CASAS ALIMENTADAS" "g" "0.09" "CAT_CASAS ALIMENTADAS" "")
   (command "_Layer" "_m" "CAT_# CASAS ALIMENTADAS" "_c" "BLANCO" "CAT_# CASAS ALIMENTADAS" "T" "CONTINUOUS" "CAT_# CASAS ALIMENTADAS" "g" "0.09" "CAT_# CASAS ALIMENTADAS" "")
   (command "_Layer" "_m" "CAT_COMERCIOS ALIMENTADOS" "_c" "VERDE" "CAT_COMERCIOS ALIMENTADOS" "T" "CONTINUOUS" "CAT_COMERCIOS ALIMENTADOS" "g" "0.09" "CAT_COMERCIOS ALIMENTADOS" "")
   (command "_Layer" "_m" "CAT_# COMERCIOS ALIMENTADOS" "_c" "BLANCO" "CAT_# COMERCIOS ALIMENTADOS" "T" "CONTINUOUS" "CAT_# COMERCIOS ALIMENTADOS" "g" "0.09" "CAT_# COMERCIOS ALIMENTADOS" "")
   (command "_Layer" "_m" "CAT_EDIFICIOS ALIMENTADOS" "_c" "VERDE" "CAT_EDIFICIOS ALIMENTADOS" "T" "CONTINUOUS" "CAT_EDIFICIOS ALIMENTADOS" "g" "0.09" "CAT_EDIFICIOS ALIMENTADOS" "")
   (command "_Layer" "_m" "CAT_# EDIFICIOS ALIMENTADOS" "_c" "BLANCO" "CAT_# EDIFICIOS ALIMENTADOS" "T" "CONTINUOUS" "CAT_# EDIFICIOS ALIMENTADOS" "g" "0.09" "CAT_# EDIFICIOS ALIMENTADOS" "")
   (command "_Layer" "_m" "CAT_# DEPARTAMENTOS ALIMENTADOS" "_c" "BLANCO" "CAT_# DEPARTAMENTOS ALIMENTADOS" "T" "CONTINUOUS" "CAT_# DEPARTAMENTOS ALIMENTADOS" "g" "0.09" "CAT_# DEPARTAMENTOS ALIMENTADOS" "")
   (command "_Layer" "_m" "CAT_LAPIDAS" "_c" "BLANCO" "CAT_LAPIDAS" "T" "CONTINUOUS" "CAT_LAPIDAS" "g" "0.09" "CAT_LAPIDAS" "")
   (command "_Layer" "_m" "CAT_NODO OPTICO" "_c" "AZUL" "CAT_NODO OPTICO" "T" "CONTINUOUS" "CAT_NODO OPTICO" "g" "0.09" "CAT_NODO OPTICO" "")
   (command "_Layer" "_m" "CAT_FUENTE PODER" "_c" "BLANCO" "CAT_FUENTE DE PODER" "T" "CONTINUOUS" "CAT_FUENTE DE PODER" "g" "0.09" "CAT_FUENTE DE PODER" "")
   (command "_Layer" "_m" "CAT_PUNTO SUMINISTRO" "_c" "BLANCO" "CAT_PUNTO SUMINISTRO" "T" "CONTINUOUS" "CAT_PUNTO SUMINISTRO" "g" "0.09" "CAT_PUNTO SUMINISTRO" "")
   (command "_Layer" "_m" "CAT_MANZANAS" "_c" "BLANCO" "CAT_MANZANAS" "T" "CONTINUOUS" "CAT_MANZANAS" "g" "0.09" "CAT_MANZANAS" "")
   (command "_Layer" "_m" "CAT_LOTES" "_c" "BLANCO" "CAT_LOTES" "T" "CONTINUOUS" "CAT_LOTES" "g" "0.09" "CAT_LOTES" "")
   (command "_Layer" "_m" "CAT_LIMITE LOTES" "_c" "BLANCO" "CAT_LIMITE LOTES" "T" "CONTINUOUS" "CAT_LIMITE LOTES" "g" "0.09" "CAT_LIMITE LOTES" "")
   (command "_Layer" "_m" "CAT_CODIGO POSTES" "_c" "BLANCO" "CAT_CODIGO POSTES" "T" "CONTINUOUS" "CAT_CODIGO POSTES" "g" "0.09" "CAT_CODIGO POSTES" "")
   (command "_Layer" "_m" "CAT_CABLE 500" "_c" "AZUL" "CAT_CABLE 500" "T" "TRAZOS" "CAT_CABLE 500" "g" "0.09" "CAT_CABLE 500" "")
   (command "_Layer" "_m" "CAT_CABLE EXPRESO" "_c" "ROJO" "CAT_CABLE EXPRESO" "T" "TRAZOS" "CAT_CABLE EXPRESO" "g" "0.09" "CAT_CABLE EXPRESO" "")
   (command "_Layer" "_m" "CAT_DATA AMPLIFICADORES" "_c" "BLANCO" "CAT_DATA AMPLIFICADORES" "T" "CONTINUOUS" "CAT_DATA AMPLIFICADORES" "g" "0.09" "CAT_DATA AMPLIFICADORES" "")
   (command "_Layer" "_m" "CAT_INFO ACTIVOS" "_c" "BLANCO" "CAT_INFO ACTIVOS" "T" "CONTINUOUS" "CAT_INFO ACTIVOS" "g" "0.09" "CAT_INFO ACTIVOS" "")
   (command "_Layer" "_m" "CAT_CAMARAS" "_c" "AZUL" "CAT_CAMARAS" "T" "CONTINUOUS" "CAT_CAMARAS" "g" "0.09" "CAT_CAMARAS" "")
   (command "_Layer" "_m" "CAT_ACOPLADORES" "_c" "BLANCO" "CAT_ACOPLADORES" "T" "CONTINUOUS" "CAT_ACOPLADORES" "g" "0.09" "CAT_ACOPLADORES" "")
   (command "_Layer" "_m" "CAT_URBANIZACIONES" "_c" "AZUL" "CAT_URBANIZACIONES" "T" "CONTINUOUS" "CAT_URBANIZACIONES" "g" "0.09" "CAT_URBANIZACIONES" "")
   (princ)
   (eval "LISTO MEN")
)
