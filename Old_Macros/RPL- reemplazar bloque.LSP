; TIP1022.LSP: REPLACE.LSP   Replace Blocks   (c)1994, Steven Hauk

(defun c:RPL (/ ENT1 BL1 NWNM OLD ODNM)
   (prompt "Select blocks to replace: ")
   (setq ENT1 (ssget))
   (setq NEWBL (getstring "\nEnter new block name: "))
   (command "insert" NEWBL nil)
   (setq N (sslength ENT1))
   (setq I 0)
   (repeat N
      (setq BL1 (entget (ssname ENT1 I)))
      (setq NWNM (cons 2 NEWBL))
      (setq OLD (assoc 2 BL1))
      (setq ODNM (cdr OLD))
      (entmod (subst NWNM OLD BL1))
      (setq I (1+ I))
   )
   (prin1)
)
(defun c:SSPREPL (/ ENT1 BL1 NWNM OLD ODNM)
   (prompt "Select objects: ")
   (setq ENT1 (ssget))
   (prompt "\nSelect typical old block: ")
   (setq E0 (entsel))
   (setq E1 (entget (car E0)))
   (setq E2N (cdr (assoc 2 E1)))
   (setq E2L (cdr (assoc 8 E1)))
   (setq NEWBL (getstring "\nEnter new block name: "))
   (command "insert" NEWBL nil)
   (setq N (sslength ENT1))
   (setq I 0)
   (repeat N
      (setq BL1 (entget (ssname ENT1 I)))
      (setq NWNM (cons 2 NEWBL))
      (setq OLD (assoc 2 BL1))
      (setq OLDBL (cdr OLD))
      (setq OLDL (assoc 8 BL1))
      (setq OLDLL (cdr OLDL))
      (if (and (equal E2N OLDBL)(equal E2L OLDLL))
         (progn
            (setq ODNM (cdr OLD))
            (entmod (subst NWNM OLD BL1))
         )
      )
      (setq I (1+ I))
   )
   (prin1)
)
(defun c:SSNREPL (/ ENT1 BL1 NWNM OLD ODNM)
   (prompt "Select objects: ")
   (setq ENT1 (ssget))
   (setq OLDBL (strcase (getstring "\nEnter old block name: ")))
   (setq NEWBL (getstring "\nEnter new block name: "))
   (command "insert" NEWBL NIL)
   (setq N (sslength ENT1))
   (setq I 0)
   (repeat N

      (setq BL1 (entget (ssname ENT1 I)))
      (setq NWNM (cons 2 NEWBL))
      (setq OLD (assoc 2 BL1))
      (setq OLD1 (cdr OLD))
      (if (equal OLD1 OLDBL)(progn
            (setq ODNM (cdr OLD))
            (entmod (subst NWNM OLD BL1))
         )
      )
      (setq I (1+ I))
   )
   (prin1)
)
(defun c:SSXREPL (/ ENT1 BL1 NWNM OLD ODNM)
   (prompt "\nSelect typical old block: ")
   (setq E0 (entsel))
   (setq E1 (entget (car E0)))
   (setq E2N (cdr (assoc 2 E1)))
   (setq E2L (cdr (assoc 8 E1)))
   (setq ENT1 (ssget "X" (list (cons 0 "INSERT")(cons 2 E2N))))
   (setq NEWBL (Getstring "\nEnter new block name: "))
   (command "insert" NEWBL nil)
   (setq N (sslength ENT1))
   (setq I 0)
   (repeat N
      (setq BL1 (entget (ssname ENT1 I)))
      (setq NWNM (cons 2 NEWBL))
      (setq OLD (assoc 2 BL1))
      (setq OLDBL (cdr OLD))
      (setq OLDL (assoc 8 BL1))
      (setq OLDLL (cdr OLDL))
      (if (and (equal E2N OLDBL)(equal E2L OLDLL))
         (progn
            (setq ODNM (cdr OLD))
            (entmod (subst NWNM OLD BL1))
         )
      )
      (setQ I (1+ I))
   )
   (prin1)
);end replace.lsp
